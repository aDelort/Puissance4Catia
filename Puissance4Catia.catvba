Attribute VB_Name = "ModuleErase"
Dim timeArray(50)
Dim time_ind As Integer

Public Sub eraseTokens()
time_ind = 0
If tokensDisplayed Then
    tokensDisplayed = False

    Dim productDocument As productDocument
    Set productDocument = CATIA.ActiveDocument
    
    Dim selection As selection
    Set selection = productDocument.selection

    selection.Clear

    Dim product As product
    Set product = productDocument.product

    Dim constraints As constraints
    Set constraints = product.Connections("CATIAConstraints")

    For i = 1 To nbYellowTokens
        selection.Add product.Products.Item("jetonJaune." & i)
        selection.Add constraints.Item("JetonJaune" & i & "LongX")
        selection.Add constraints.Item("JetonJaune" & i & "LongY")
        selection.Add constraints.Item("JetonJaune" & i & "LongZ")
        selection.Add constraints.Item("JetonJaune" & i & "AngleX")
        selection.Add constraints.Item("JetonJaune" & i & "AngleY")
        selection.Delete
        selection.Clear
    Next i

    For i = 1 To nbRedTokens
        selection.Add product.Products.Item("jetonRouge." & i)
        selection.Add constraints.Item("JetonRouge" & i & "LongX")
        selection.Add constraints.Item("JetonRouge" & i & "LongY")
        selection.Add constraints.Item("JetonRouge" & i & "LongZ")
        selection.Add constraints.Item("JetonRouge" & i & "AngleX")
        selection.Add constraints.Item("JetonRouge" & i & "AngleY")
        selection.Delete
        selection.Clear
    Next i

End If
End Sub

Attribute VB_Name = "ModuleInit"
Global nbRedTokens, nbYellowTokens, nbRedTokensPlayed, nbYellowTokensPlayed As Integer
Global tokensDisplayed, yellowPlayerTurn As Boolean
Global tokensPlayed(7) As Integer

Public Sub importTokens()
If Not tokensDisplayed Then
    tokensDisplayed = True
    Set productDocument = CATIA.ActiveDocument
    
    Set product = productDocument.product
    
    Set params = product.Parameters
    
    Set products1 = product.Products
    
    Dim nbTokens As Integer
    nbTokens = params.Item("nombre_trous_horizontal").Value * params.Item("nombre_trous_vertical").Value
    
    nbYellowTokens = (nbTokens + 1) \ 2
    nbRedTokens = nbTokens \ 2
    nbYellowTokensPlayed = 0
    nbRedTokensPlayed = 0
    
    yellowPlayerTurn = True
    
    For i = 1 To 7
        tokensPlayed(i) = 0
    Next i
    
    
    'Adding the tokens
    Dim arrayOfVariantOfBSTR1()
    ReDim arrayOfVariantOfBSTR1(nbTokens)
    For i = 0 To nbYellowTokens - 1
        arrayOfVariantOfBSTR1(i) = ".\JetonJaune.CATPart"
    Next i
    For i = nbYellowTokens To nbTokens - 1
        arrayOfVariantOfBSTR1(i) = ".\JetonRouge.CATPart"
    Next i
    
    Set products1Variant = products1
    products1Variant.AddComponentsFromFiles arrayOfVariantOfBSTR1, "All"
    
    
    
    'Initial positions
    Dim isYellowToken As Boolean
    Dim color As String
    Dim indexYellowToken, indexRedToken, indexToken As Integer
    indexYellowToken = 0
    indexRedToken = 0
    
    
    Set referenceGrilleZX = product.CreateReferenceFromName("puissance4/grille.1/!grille/Plan zx")
    Set referenceGrilleXY = product.CreateReferenceFromName("puissance4/grille.1/!Corps principal/Plan.5")
    Set referenceGrilleYZ = product.CreateReferenceFromName("puissance4/grille.1/!grille/Plan yz")
    Set constraints = product.Connections("CATIAConstraints")
    Set selectionToHide = productDocument.selection
    Set visPropertySet1 = selectionToHide.VisProperties
    
    For i = 1 To nbTokens
        isYellowToken = (i Mod 2 = 1)
        If isYellowToken Then
            color = "Jaune"
            indexYellowToken = indexYellowToken + 1
            indexToken = indexYellowToken
        Else
            color = "Rouge"
            indexRedToken = indexRedToken + 1
            indexToken = indexRedToken
        End If
        
        Set referenceJetonOrigine = product.CreateReferenceFromName("puissance4/jeton" & color & "." & indexToken & "/!Corps principal/Extrusion.37/Esquisse.1/Repère/Origine")
        
        'Contrainte angulaire du jeton x
        Set referenceJetonXY = product.CreateReferenceFromName("puissance4/jeton" & color & "." & indexToken & "/!jeton" & color & "/Plan xy")
        
        Set constraintAngleX = constraints.AddBiEltCst(catCstTypeAngle, referenceGrilleZX, referenceJetonXY)
        
        Set angleX = constraintAngleX.Dimension
        
        angleX.Value = 0
        
        constraintAngleX.AngleSector = catCstAngleSector0
        constraintAngleX.Name = "Jeton" & color & indexToken & "AngleX"
        selectionToHide.Add constraintAngleX
        
        'Contrainte angulaire du jeton y
        Set referenceJetonYZ = product.CreateReferenceFromName("puissance4/jeton" & color & "." & indexToken & "/!jeton" & color & "/Plan yz")
        
        Set constraintAngleY = constraints.AddBiEltCst(catCstTypeAngle, referenceGrilleYZ, referenceJetonYZ)
        
        Set angleY = constraintAngleY.Dimension
        
        angleY.Value = indexToken * 10
        
        constraintAngleY.AngleSector = catCstAngleSector0
        constraintAngleY.Name = "Jeton" & color & indexToken & "AngleY"
        selectionToHide.Add constraintAngleY
        
        ' Contrainte en y
        Set constraintY = constraints.AddBiEltCst(catCstTypeDistance, referenceGrilleZX, referenceJetonOrigine)
        constraintY.Dimension.Value = 6 * (indexToken - 1) - 57.373
        constraintY.Orientation = catCstOrientSame
        constraintY.Name = "Jeton" & color & indexToken & "LongY"
        selectionToHide.Add constraintY
        
        ' Contrainte en z
        Set constraintZ = constraints.AddBiEltCst(catCstTypeDistance, referenceGrilleXY, referenceJetonOrigine)
        constraintZ.Dimension.Value = 0
        constraintZ.Orientation = catCstOrientSame
        constraintZ.Name = "Jeton" & color & indexToken & "LongZ"
        selectionToHide.Add constraintZ
        
        ' Contrainte en x
        Set constraintX = constraints.AddBiEltCst(catCstTypeDistance, referenceGrilleYZ, referenceJetonOrigine)
        If isYellowToken Then
            constraintX.Dimension.Value = -80
        Else
            constraintX.Dimension.Value = params.Item("largeur").Value + 80
        End If
        constraintX.Orientation = catCstOrientSame
        constraintX.Name = "Jeton" & color & indexToken & "LongX"
        selectionToHide.Add constraintX
        
        'Hiding constraints
        Set visPropertySet1 = visPropertySet1.Parent
        visPropertySet1.SetShow 1
        selectionToHide.Clear
    Next i

    product.Update
    
End If
End Sub

Attribute VB_Name = "ModulePlay"
Public Sub play_positionN(N)

If tokensDisplayed Then

    Set productDocument = CATIA.ActiveDocument
    
    Set product = productDocument.product
    
    Set params = product.Parameters
    
    If tokensPlayed(N) < params.Item("nombre_trous_vertical").Value Then
    
        Dim yellowPlayerTurn As Boolean
        Dim color As String
    
        yellowPlayerTurn = (nbYellowTokensPlayed = nbRedTokensPlayed)
        If yellowPlayerTurn Then
            color = "Jaune"
            indexToken = nbYellowTokens - nbYellowTokensPlayed
        Else
            color = "Rouge"
            indexToken = nbRedTokens - nbRedTokensPlayed
        End If
            
        
        Set constraints = product.Connections("CATIAConstraints")
    
        constraints.Item("Jeton" & color & indexToken & "LongX").Dimension.Value = (N - 1 / 2) * params.Item("distance_centre_trous_horizontal").Value + (3 / 2) * params.Item("epaisseur_plastique_fin").Value
        constraints.Item("Jeton" & color & indexToken & "LongY").Dimension.Value = (tokensPlayed(N) + 1 / 2) * params.Item("distance_centre_trous_vertical").Value + params.Item("epaisseur_plastique_fin").Value
        constraints.Item("Jeton" & color & indexToken & "AngleX").Dimension.Value = 90
        constraints.Item("Jeton" & color & indexToken & "AngleY").Dimension.Value = 0
    
        product.Update
        
        If yellowPlayerTurn Then
             nbYellowTokensPlayed = nbYellowTokensPlayed + 1
        Else
             nbRedTokensPlayed = nbRedTokensPlayed + 1
        End If
        tokensPlayed(N) = tokensPlayed(N) + 1
    End If
End If

End Sub

Attribute VB_Name = "ModuleShow"
Sub CATMain()
commandes.Show
End Sub

Attribute VB_Name = "commandes"
Attribute VB_Base = "0{B2BF618F-E2DE-4EBF-BE25-95344584FF3B}{6A24D726-D845-429F-A7BF-44C567195B9E}"
Attribute VB_GlobalNameSpace = False
Attribute VB_Creatable = False
Attribute VB_PredeclaredId = True
Attribute VB_Exposed = False
Attribute VB_TemplateDerived = False
Attribute VB_Customizable = False
Private Sub button_erase_Click()
Call eraseTokens
End Sub

Private Sub button_init_Click()
Call importTokens
End Sub

Private Sub button_position1_Click()
play_positionN (1)
End Sub

Private Sub button_position2_Click()
play_positionN (2)
End Sub

Private Sub button_position3_Click()
play_positionN (3)
End Sub

Private Sub button_position4_Click()
play_positionN (4)
End Sub

Private Sub button_position5_Click()
play_positionN (5)
End Sub

Private Sub button_position6_Click()
play_positionN (6)
End Sub

Private Sub button_position7_Click()
play_positionN (7)
End Sub
